# coding: UTF-8

import sys
import os.path

# get the path of the current python script
current_path = os.path.dirname(os.path.realpath(__file__))

# check if this path belongs to the PYTHONPATH variable and if not add it
if not sys.path.__contains__(str(current_path)):
    sys.path.append(str(current_path))

from FreeCAD import Console, Gui
from PySide2.QtWidgets import QMessageBox
from PySide2.QtCore import Qt
from Legify.Dialog import *

if Gui.activeDocument():
    Dialog()
    Gui.activeDocument().activeView().viewAxonometric()
    Gui.SendMsgToActiveView("ViewFit")

else:
    Console.PrintMessage("No active document!\n")
    dialog = QMessageBox(QMessageBox.Warning, 'No active document!', "There is no active document!")
    dialog.setWindowModality(Qt.ApplicationModal)
    dialog.exec_()
